module devnet-study {

  namespace "http://example.com/devnet-study";
  prefix devnet-study;

  import ietf-inet-types {
    prefix inet;
  }
  import tailf-common {
    prefix tailf;
  }
  import tailf-ncs {
    prefix ncs;
  }

  description
    "Bla bla...";

  revision 2016-01-01 {
    description
      "Initial revision.";
  }

  list devnet-study {
    description "This is an RFS skeleton service";

    key name;
    leaf name {
      tailf:info "Unique service id";
      tailf:cli-allow-range;
      type string;
    }

    uses ncs:service-data;
    ncs:servicepoint devnet-study-servicepoint;

    // may replace this with other ways of refering to the devices.
    leaf device {
      type leafref {
        path "/ncs:devices/ncs:device/ncs:name";
      }
    }

    // bgp neighbor ipv4 address
    leaf bgp_neighbor_addr {
      type inet:ipv4-address;
    }

    // bgp local-as
    leaf bgp_local_as {
      type inet:as-number;
    }

    // bgp remote-as
    leaf bgp_remote_as {
      type inet:as-number;
    }
  }
}
